# -*- coding: utf-8 -*-
# (c) microelly2@freecadbuch.de 2014
#
# gnerate a frame in the draft workspace as orientation for the mapping to the drawing

import Draft

gr=App.ActiveDocument.addObject("App::DocumentObjectGroup","Hilfsrahmen")
pl = FreeCAD.Placement()
pl.Rotation.Q = (0.0,-0.0,-0.0,1.0)
pl.Base = FreeCAD.Vector(-90,90,0.0)
tt=Draft.makeRectangle(length=400,height=-276,placement=pl,face=False,support=None)
gr.addObject(tt)

pl.Base = FreeCAD.Vector(120,-125,0.0)
tt=Draft.makeRectangle(length=190,height=-60,placement=pl,face=False,support=None)


gr.addObject(tt)
