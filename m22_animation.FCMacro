import sys
sys.path.append('/home/microelly2/fc_dev/')
import mymodule
import Animation
from Animation import *

import FreeCAD
App=FreeCAD
import FreeCADGui

import FreeCADGui
Gui=FreeCADGui

import Draft
import time
import datetime

reload(Animation)


ll=20







# vectors for the moves

sk=FreeCAD.Vector(100,0,0)
sk2=FreeCAD.Vector(0,40,0)


# initial placement
rp = App.Placement(App.Vector(1,1,0),App.Rotation(App.Vector(0,0,1),0))
tp = App.Placement(App.Vector(1,1,0),App.Rotation(App.Vector(0,0,1),0))

def init1():
	import Draft
	App.newDocument("Unnamed")
	App.setActiveDocument("Unnamed")

 
	pl = FreeCAD.Placement()
	pl.Rotation.Q = (0.0,-0.0,-0.0,1.0)
	pl.Base = FreeCAD.Vector(-1.32548344135,0.938884139061,0.0)
	Draft.makeRectangle(length=2.2229462862,height=-1.14599096775,placement=pl,face=False,support=None)
	points=[FreeCAD.Vector(-0.566091835499,0.455634981394,0.0),FreeCAD.Vector(1.44974756241,-1.64304709435,0.0),FreeCAD.Vector(-2.43005299568,-1.6982755661,0.0)]
	Draft.makeWire(points,closed=True,face=False,support=None)
	FreeCAD.getDocument("Unnamed").getObject("DWire").MakeFace = True
	FreeCADGui.getDocument("Unnamed").getObject("DWire").ShapeColor = (0.00,1.00,0.00)
	FreeCADGui.getDocument("Unnamed").getObject("Rectangle").ShapeColor = (1.00,0.00,0.00)
	FreeCAD.getDocument("Unnamed").getObject("Rectangle").MakeFace = True
	points=[FreeCAD.Vector(-0.566091835499,0.455634981394,0.0),FreeCAD.Vector(1.44974756241,-1.64304709435,0.0),FreeCAD.Vector(-2.43005299568,-1.6982755661,0.0)]
	Draft.makeWire(points,closed=True,face=False,support=None)
	Gui.getDocument("Unnamed").getObject("DWire001").Visibility=False
	pl = FreeCAD.Placement()
	pl.Rotation.Q = (0.0,-0.0,-0.0,1.0)
	pl.Base = FreeCAD.Vector(-15.3152351379,75.8536605835,0.0)
	Draft.makeRectangle(length=126.597446442,height=-87.5533657074,placement=pl,face=False,support=None)
	Gui.SendMsgToActiveView("ViewFit")
def finish1():
	try:
		App.ActiveDocument=App.getDocument("Unnamed")
		Gui.ActiveDocument=Gui.getDocument("Unnamed")
		App.closeDocument("Unnamed")
		App.setActiveDocument("")
		App.ActiveDocument=None
		Gui.ActiveDocument=None
	except:
		pass





def test1():

	text=Draft.makeText(["textanzeige"],point=FreeCAD.Vector(4,60,0.0))
	FreeCADGui.getDocument("Unnamed").getObject("Text").FontSize = 10


	# the entertainer
	m=Manager()
	m.setShowTime(text)

	# place to write the film output
#	fn='/home/microelly2/pic2/AA_B'
# 	m.setOutput(fn)

	# actor 1 an rectangle, that should move - move the table
	r1=Mover("Rectangle",sk2,5,45)
# 	r1.initPlacement(rp)
	m.register(r1)

	# second  movement of the same rectangle
	r2=Mover("Rectangle",sk,25,80)
	m.register(r2)

    # actor 2  a triangle, that rotates    - drill the screw
	r3=Rotator("DWire")
	r3.initPlacement(tp)
	m.register(r3)

	tr=Tranquillizer(0.1)
	m.register(tr)
	
	# run the animation for 100 frames
##	m.run(100)
	m.run(ll)

	# bring all back to the initial position
	m.finalize(0)


def test2():
	# move along a line "Line"
	text=Draft.makeText(["textanzeige"],point=FreeCAD.Vector(4,60,0.0))
	FreeCADGui.getDocument("Unnamed").getObject("Text").FontSize = 10

	m=Manager()
	m.setShowTime(text)
	r1=Mover("Rectangle","Line",0,10)
 	r1.initPlacement(rp)
	m.register(r1)

	tr=Tranquillizer(0.1)
	m.register(tr)

	m.run(10)

	App.getDocument("Unnamed").removeObject("Text")

def test3():
	# move the line backward  "-Line"
	m=Manager()
	r1=Mover("Rectangle","-Line",0,30)
	m.register(r1)
	tr=Tranquillizer(0.1)
	m.register(tr)
	m.run(30)

def test4():
	# load m01_tests234 FCs
	# rotate clockwise and counterclockwise
	m=Manager()
	r3=Rotator("DWire")
	r3.setIntervall(10,40)
	r3.initPlacement(tp)
	r3.setRot("DWire002")
	r3.reverse()
	m.register(r3)
	r4=Rotator("DWire")
	r4.setIntervall(50,80)
	r4.setRot("DWire002")
	m.register(r4)

	# make fotos in time 10 -- 40 to output /tmp/test4_*
	f=Photographer("/tmp/test4_")
	f.setIntervall(10,40)
	m.register(f)

	# pause for 0.1 sec after each step
	tr=Tranquillizer(0.1)
	m.register(tr)
	m.run(100)


def test5():
	m=Manager()
	
	stella=Rotator('stella')
	stella.setRot('DWire')
	stella.setIntervall(50,150)
	m.register(stella)

	freek=Mover("freek_v2","Line003",10,100)
	m.register(freek)

	s2=Rotator('freek_v2')
	s2.setRot('DWire003')
	s2.setIntervall(100,140)
	s2.reverse2()
	s2.reverse()
	m.register(s2)

	freek=Mover("freek_v2","Line001",140,240)
	m.register(freek)

	s2=Rotator('freek_v2')
	s2.setRot('DWire002')
	s2.setIntervall(250,270)
	s2.reverse2()
	m.register(s2)

	freek=Mover("freek_v2","Line002",280,360)
	m.register(freek)

	f=Photographer("/tmp/test5_")
	f.setIntervall(0,450)
	m.register(f)

#	tr=Tranquillizer(0.1)
#	m.register(tr)
	m.run(440)
	m.finalize(0)

def test6():
	m=Manager()
	

	f=Mover("Schraube","Anlieferer",10,100)
	m.register(f)

	f=Mover("Schraube","Senker",130,200)
	m.register(f)

	s=Rotator('Schraube')
	s.setRot('Dreher')
	s.setIntervall(150,200)
	m.register(s)

	f=Photographer("/tmp/AA_")
	f.setIntervall(0,450)
	m.register(f)

	tr=Tranquillizer(0.01)
	m.register(tr)
	m.run(300)

	m.finalize(0)




# main
def test7():
	m=Manager()
	f=Mover("Schraube","Anlieferer",10,100)
	m.register(f)
	p=Pinner('Kiste','Schraube')
	m.register(p)

	tr=Tranquillizer(0.101)
	m.register(tr)

	m.run(100)
	m.finalize(0)


'''
Schraube verschiebt sich entlang der blauen Linie
Kiste foilgt dem Punnkt auf dem Kreis
Kreisradius von 10 auf 30
'''
def test7():
	m=Manager()
	f=Mover("Schraube","Anlieferer",10,100)
	m.register(f)

	
	st=Adjuster('Sketch','rradd','',0,10)
	st.setValues(10,30)
	m.register(st)


	p=Plugger('Kiste','Sketch')
	p.setDetail('Vertex.Point',0)

	m.register(p)

	tr=Tranquillizer(0.01)
	m.register(tr)

	m.run(100)
	m.finalize(0)


if 0:
	init1()
	test1()
	finish1()

if 0:
	test2()
if 0:

	test3()
if 0:
	test4()


if 0:
	test5()
if 0:
	test6()

test7()
